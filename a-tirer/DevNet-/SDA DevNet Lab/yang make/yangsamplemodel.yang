module ietf-sub-interface{
    namespace "hhtp://reseauxnet.fr";
    prefix "ietf-sub-interface";

    organization "SDACO";
    contact "technique@reseauxnet.fr";
    description
    "First yang module created by SDA";

    revision 30-08-2021 {
        description "Initial version - creation - Ref : "https://www.youtube.com/watch?v=AjmyDvKyH2w" ";
    }

    typedef ipv4-prefix {
    type string {
      pattern
         '(([0-9]|[1-9][0-9]|1[0-9][0-9]|2[0-4][0-9]|25[0-5])\.){3}'
       +  '([0-9]|[1-9][0-9]|1[0-9][0-9]|2[0-4][0-9]|25[0-5])'
       + '/(([0-9])|([1-2][0-9])|(3[0-2]))';
    }
  }
    container sub-interface{
        list sub-interface{
            key "name";
            leaf name {
                type ipv4-prefix;
            }

            leaf ipaddress{
                type string;
            }

            leaf netmask{
                type ipv4-prefix;
            }
        }
    }


}
